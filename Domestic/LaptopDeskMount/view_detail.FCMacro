import FreeCAD as App
import FreeCADGui as Gui

d = App.getDocument("LaptopDeskMount")
d.Environment.ViewObject.Visibility = True
d.TableDetail.ViewObject.Visibility = True
for o in d.TableDetail.Group:
    o.ViewObject.Visibility = True
for o in d.WholeTable.Group:
    o.ViewObject.Visibility = False
d.WholeTable.ViewObject.Visibility = False
d.Laptop.ViewObject.Visibility = True
d.LaptopBase.ViewObject.Visibility = True
d.LaptopBase.ViewObject.Transparency = 65
d.LaptopScreen.ViewObject.Visibility = False
d.TabletopDetail.ViewObject.Transparency = 78
d.PrintedParts.ViewObject.Visibility = True
d.HolderLeft.ViewObject.Visibility = True
for feature in d.HolderLeft.Group:
    if feature.TypeId.startswith("PartDesign::") or feature.TypeId == "Sketcher::SketchObject":
        feature.ViewObject.Visibility = feature == d.HolderLeft.Tip
d.HolderLeft.Tip.ViewObject.Visibility = True
d.HolderRight.ViewObject.Visibility = True
d.FeltPads.ViewObject.Visibility = True
for o in d.FeltPads.Group:
    o.ViewObject.Visibility = True
d.FitSamples.ViewObject.Visibility = False
d.ClampFitSample.ViewObject.Visibility = False
Gui.activeDocument().activeView().viewAxonometric()
Gui.activeDocument().activeView().fitAll()
